;;; LAYNUM.lsp - Auto layout numbering inside a circle
;;; Commands: LAYNUM (setup), LAYNUMUPD (manual update), LAYNUMOFF (remove all)

(vl-load-com)

(defun laynum:doc ()
  (vla-get-ActiveDocument (vlax-get-acad-object))
)

;; Sorted list of (taborder . name) for all paper space layouts
(defun laynum:getlist ( / lst)
  (vlax-for lay (vla-get-Layouts (laynum:doc))
    (if (> (vla-get-TabOrder lay) 0)
      (setq lst (cons (cons (vla-get-TabOrder lay) (vla-get-Name lay)) lst))
    )
  )
  (vl-sort lst '(lambda (a b) (< (car a) (car b))))
)

;; Delete everything on layer LAYNUM in all layouts
(defun laynum:clear ( / del)
  (vlax-for lay (vla-get-Layouts (laynum:doc))
    (if (> (vla-get-TabOrder lay) 0)
      (vlax-for obj (vla-get-Block lay)
        (if (= (strcase (vla-get-Layer obj)) "LAYNUM")
          (setq del (cons obj del))
        )
      )
    )
  )
  (foreach obj del
    (vl-catch-all-apply 'vla-delete (list obj))
  )
)

;; Rebuild markers in every layout
(defun laynum:update ( / pt h r blk c txt)
  (setq pt (vlax-ldata-get "LAYNUM" "PT")
        h  (vlax-ldata-get "LAYNUM" "H")
        r  (vlax-ldata-get "LAYNUM" "R")
  )
  (if (and pt h r)
    (progn
      (vla-add (vla-get-Layers (laynum:doc)) "LAYNUM")
      (laynum:clear)
      (foreach item (laynum:getlist)
        (setq blk (vla-get-Block (vla-Item (vla-get-Layouts (laynum:doc)) (cdr item))))
        (setq c (vla-AddCircle blk (vlax-3d-point pt) r))
        (vla-put-Layer c "LAYNUM")
        (setq txt (vla-AddText blk (itoa (car item)) (vlax-3d-point pt) h))
        (vla-put-Layer txt "LAYNUM")
        (vla-put-Alignment txt 10) ; middle-center
        (vla-put-TextAlignmentPoint txt (vlax-3d-point pt))
      )
    )
  )
  (princ)
)

;; Reactor callback
(defun laynum:cmdEnded (rx info / cur)
  (if (and (not laynum:busy) (vlax-ldata-get "LAYNUM" "PT"))
    (progn
      (setq laynum:busy T)
      (vl-catch-all-apply
        '(lambda ()
           (setq cur (laynum:getlist))
           (if (not (equal cur laynum:cache))
             (progn (setq laynum:cache cur) (laynum:update))
           )
         )
      )
      (setq laynum:busy nil)
    )
  )
  (princ)
)

(defun laynum:start ()
  (if (not laynum:rx)
    (setq laynum:rx
      (vlr-command-reactor nil '((:vlr-commandEnded . laynum:cmdEnded))))
  )
  (princ)
)

(defun c:LAYNUM ( / pt h r oh or)
  (if (or (= (getvar "TILEMODE") 1) (/= (getvar "CVPORT") 1))
    (alert "Go to a layout tab, outside any viewport, then run LAYNUM.")
    (if (setq pt (getpoint "\nPick number location: "))
      (progn
        (setq oh (cond ((vlax-ldata-get "LAYNUM" "H")) (T 5.0)))
        (setq h (getreal (strcat "\nText height <" (rtos oh) ">: ")))
        (if (not h) (setq h oh))
        (setq or (cond ((vlax-ldata-get "LAYNUM" "R")) (T (* h 1.2))))
        (setq r (getreal (strcat "\nCircle radius <" (rtos or) ">: ")))
        (if (not r) (setq r or))
        (vlax-ldata-put "LAYNUM" "PT" (list (car pt) (cadr pt) 0.0))
        (vlax-ldata-put "LAYNUM" "H" h)
        (vlax-ldata-put "LAYNUM" "R" r)
        (laynum:start)
        (setq laynum:cache (laynum:getlist))
        (laynum:update)
        (princ "\nLayout numbering is active.")
      )
    )
  )
  (princ)
)

(defun c:LAYNUMUPD ()
  (laynum:start)
  (setq laynum:cache (laynum:getlist))
  (laynum:update)
  (princ)
)

(defun c:LAYNUMOFF ()
  (laynum:clear)
  (if (vlax-ldata-get "LAYNUM" "PT") (vlax-ldata-delete "LAYNUM" "PT"))
  (if laynum:rx (progn (vlr-remove laynum:rx) (setq laynum:rx nil)))
  (princ "\nLayout numbering removed.")
  (princ)
)

(princ "\nLAYNUM loaded. Commands: LAYNUM, LAYNUMUPD, LAYNUMOFF")
(princ)
